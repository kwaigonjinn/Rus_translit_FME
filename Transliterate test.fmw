FME workspace Transliterate test.fmw

Parameters:
- SourceDataset_XLSXR = C:\Users\wole1\Desktop\bankomat_all_27.10.2017.xls   # Source Microsoft Excel File(s)
- SourceDataset_XLSXR_4 = http://www.gazprombank.ru/atm/downloads/bankomat_all_29.12.2017.xls   # Source Microsoft Excel File(s)

Readers:
- XLSXR_2: XLSXR from $(SourceDataset_XLSXR)
- XLSXR_1: XLSXR from $(SourceDataset_XLSXR_4)

AttributeManager
    ATTR_TABLE:
      RENAME_SET_VALUE Регион, область > region
      RENAME_SET_VALUE Название населен пункта > city
      RENAME_SET_VALUE Адрес > address
      RENAME_SET_VALUE Место расположения > place
      RENAME_SET_VALUE Вид банкомата > atmType
      RENAME_SET_VALUE Режим работы > openingHours
      RENAME_SET_VALUE Вид карты > cardType
      RENAME_SET_VALUE Валюта > currency
      RENAME_SET_VALUE Cash-in > cashIn
      RENAME_SET_VALUE Обмен валюты > exchange
      RENAME_SET_VALUE Координаты - широта > latitude
      RENAME_SET_VALUE Координаты - долгота > longitude
      REMOVE Принадлежность филиалу
    -> AttributeEncoder
AttributeEncoder
    DEST_ENCODING = fme-system
    ATTRCHOICE = All Attributes
    TREAT_AS_BYTES = Honor Encoding
    -> Tester
PythonCaller_2_Output: Inspector

Bookmark: Get ATM data
  Download exel file from 
  http://www.gazprombank.ru/atm/downloads/bankomat_all_29.12.2017.xls
Лист1/header (reader XLSXR_1)
    attributes: Регион, область char(14), Название населен пункта char(25), Адрес char(160), Место расположения char(203), Вид банкомата char(4), Режим работы char(117), Вид карты char(41), Валюта char(14), Cash-in char(4), Обмен валюты char(11), Координаты - широта number(10,6), Координаты - долгота number(10,6), Принадлежность филиалу char(43)
    -> AttributeManager

Bookmark: Transliteration
Note: TEST if address value is empty
Tester
    TEST_MODE = Automatic
    TEST_DESCRIPTION = ""
    TEST_CLAUSE = TEST address ATTRIBUTE_IS_MISSING ""
    BOOL_OP = OR
    PASSED -> PythonCaller_2_Output
    FAILED -> PythonCaller_2

Bookmark: Transliterate 'address' script
  Need to implemented in script:
  charachters SHCH, SH, CH and so on, in the beginning of word
PythonCaller_2
    NEW_ATTRIBUTES = latin_address
    PYTHONSYMBOL = Translite
    PYTHONSOURCE:
      import string
      import fme
      import fmeobjects

      # WARNING Put Tester transformer to exclude empty values of tranliterated attribute before PythonCaller, otherwise, translation return an error

      def Translite(feature):

          #Создаём словарь

          has = {'А':'A','а':'a','Б':'B', 'б':'b', 'В':'V', 'в':'v', 'Г':'G', 'г':'g', 'Д':'D', 'д':'d', 'Е':'E', 'е':'e', 'Ё':'E', 'ё':'e', 'Ж':'Zh', 'ж':'zh', 'З':'Z', 'з':'z', 'И':'I', 'и':'i', 'Й':'Y', 'й':'y', 'К':'K', 'к':'k', 'Л':'L', 'л':'l', 'М':'M', 'м':'m', 'Н':'N', 'н':'n', 'О':'O', 'о':'o', 'П':'P', 'п':'p', 'Р':'R', 'р':'r', 'С':'S', 'с':'s', 'Т':'T', 'т':'t', 'У':'U', 'у':'u', 'Ф':'F', 'ф':'f', 'Х':'Kh', 'х':'kh', 'Ц':'Ts', 'ц':'ts', 'Ч':'Ch', 'ч':'ch', 'Ш':'Sh', 'ш':'sh', 'Щ':'Shch', 'щ':'shch', 'Ы':'Y', 'ы':'y', 'Э':'E', 'э':'e', 'Ю':'Y', 'ю':'y', 'Я':'Ya', 'я':'ya', 'Ъ':"'", 'ъ':"'", 'Ь':"'", 'ь':"'"}

          #put data to 't_Val'
          t_Val=feature.getAttribute('address')

          #replace multiple whitespaces with single
          t_Val=" ".join(t_Val.split())

          #trim
          t_Val=t_Val.strip()

          #Замена её после ьъ
          t_Val=t_Val.replace('ье','ye')

          t_Val=t_Val.replace('ьё','ye')

          t_Val=t_Val.replace('ьЁ','YE')

          t_Val=t_Val.replace('ьЕ','YE')

          #Заменяем в строке Е и Ё для начало слова

          str_j=t_Val.split(' ')

          t_Val=''

          for item in str_j:

              if (item[0]=='е' or item[0]=='ё'):

                  t_Val=t_Val+'ye'+item[1:]

              elif (item[0]=='Е' or item[0]=='Ё'):

                  t_Val=t_Val+'YE'+item[1:]

              else:

                  t_Val=t_Val+item[:]

              t_Val=t_Val+' '

          #Разбираем строку

          res=''

          for char in t_Val:

              if has.has_key(char):

                  res=res+has[char]

              else:

                  res=res+char

          #put data from 'res' to the new attribute
          feature.setAttribute("latin_address", res)
    -> PythonCaller_2_Output
